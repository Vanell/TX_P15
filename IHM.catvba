Attribute VB_Name = "Gen_XML"
Sub CATMain()

'Définition du document de travail
Set productDocument1 = CATIA.ActiveDocument
Set product1 = productDocument1.Product
Set products1 = product1.Products

'Definition des variables utilisées
Dim w As Double
Dim p As Double
Dim r As Double
Dim PI As Double
PI = 4 * Atn(1)
Dim i As Integer

'Création du XML, entête
Set xmlDoc = CreateObject("Microsoft.XMLDOM")
Set oCreation = xmlDoc.createProcessingInstruction("xml", "version='1.0' encoding='ISO-8859-1'")
xmlDoc.InsertBefore oCreation, xmlDoc.childNodes.Item(0)
Set root = xmlDoc.createElement("PRODUCT")
xmlDoc.appendChild (root)

For i = 1 To products1.Count
    Set product2 = products1.Item(i)
    Dim myArray(11)
    product2.Position.GetComponents myArray
   
    'Calcul des angles en radian
        'Rotation suivant Y
    If (1 - (myArray(6)) * (myArray(6)) <= 0.000000000001) And (1 - (myArray(6)) * (myArray(6)) >= -0.000000000001) Then
        If myArray(6) > 0 Then
            p = PI / 2
        End If
        If myArray(6) < 0 Then
            p = -PI / 2
        End If
    Else
        p = Atn(myArray(6) / Sqr(1 - (myArray(6)) * (myArray(6))))
    End If
        
        'Rotation suivant X
    If ((myArray(8) / Cos(p)) <= 0.000000000001) And ((myArray(8) / Cos(p)) >= -0.000000000001) Then
        w = PI / 2
    Else
        If myArray(8) <= 0.000000000001 And myArray(8) >= -0.000000000001 Then
            w = PI / 2
        ElseIf Cos(p) <= 0.000000000001 And Cos(p) >= -0.000000000001 Then
            w = 0
        Else
            w = Atn(Sqr(1 - (myArray(8) / Cos(p)) * (myArray(8) / Cos(p))) / (myArray(8) / Cos(p)))
        End If
    End If
        
        'Rotation suivant Z
    If ((myArray(0) / Cos(p)) <= 0.000000000001) And ((myArray(0) / Cos(p)) >= -0.000000000001) Then
        r = PI / 2
    Else
        If myArray(0) <= 0.000000000001 And myArray(0) >= -0.000000000001 Then
            r = PI / 2
        ElseIf Cos(p) <= 0.000000000001 And Cos(p) >= -0.000000000001 Then
            r = 0
        Else
            r = Atn(Sqr(1 - (myArray(0) / Cos(p)) * (myArray(0) / Cos(p))) / (myArray(0) / Cos(p)))
        End If
    End If

    'Angle en Rad vers Deg
    p = (p * 180 / PI) Mod 180
    r = (r * 180 / PI) Mod 180
    w = (w * 180 / PI) Mod 180
    
'Création de la ligne de coordonnées XML
    If myArray(11) <> 0 Then
        Set posiElmt = xmlDoc.createElement("POSI")
        posiElmt.SetAttribute "x", Round(myArray(9), 2)
        posiElmt.SetAttribute "y", Round(myArray(10), 2)
        posiElmt.SetAttribute "z", Round(myArray(11), 2)
        posiElmt.SetAttribute "w", Round(w, 2)
        posiElmt.SetAttribute "p", Round(p, 2)
        posiElmt.SetAttribute "r", Round(r, 2)
        posiElmt.SetAttribute "config_data", "N, ,0,0"
        root.appendChild (posiElmt)
    End If

Next i

Set rdr = CreateObject("MSXML2.SAXXMLReader")
Set wrt = CreateObject("MSXML2.MXXMLWriter")
Set oStream = CreateObject("ADODB.STREAM")
oStream.Open
oStream.Charset = "ISO-8859-1"
 
wrt.indent = True
wrt.Encoding = "ISO-8859-1"
wrt.Output = oStream
Set rdr.contentHandler = wrt
Set rdr.errorHandler = wrt
rdr.Parse xmlDoc
wrt.Flush
 
oStream.SaveToFile "C:\Gen_XML\xml\" & product1.Name & ".xml", 2
 
Set rdr = Nothing
Set wrt = Nothing
Set xmlDoc = Nothing

'Dim objUserEnvVars As Object
'Set objUserEnvVars = CreateObject("WScript.Shell").Environment("filenamexml")
'objUserEnvVars.Item("filename") = product1.Name & ".xml"
'MsgBox (objUserEnvVars.Item)

'SetEnvironmentVariable "filenamexml", "filename"
'MsgBox (Environ("filenamexml"))


'Lancement du fichier tri python
Dim dx As Double
dx = -150
Dim dy As Double
dy = -150
Dim RetVal As Variant
Dim stExecute As String: stExecute = """C:\Python33\python.exe"""
Dim stFile As String: stFile = "c:\Gen_XML\tri_macro.py c:\Gen_XML\xml\" & product1.Name & ".xml " & dx & " " & dy
Dim stFull As String: stFull = stExecute & " " & stFile
RetVal = Shell(stFull & " DISPLAY", vbNormalFocus)

End Sub

Attribute VB_Name = "UserForm1"
Attribute VB_Base = "0{5CB7CE02-9645-4E2F-BC34-25B0F917DBFC}{DBF10711-3DAD-405F-ACD8-F05B0A3A2A07}"
Attribute VB_GlobalNameSpace = False
Attribute VB_Creatable = False
Attribute VB_PredeclaredId = True
Attribute VB_Exposed = False
Attribute VB_TemplateDerived = False
Attribute VB_Customizable = False
Private Sub cmdExit_Click()
Dim oSelection ' As Selection
' vidage de la sélection
Set oSelection = CATIA.ActiveDocument.Selection
oSelection.Clear
'fermeture de l'IHM
UserForm1.Hide
End Sub

Private Sub cmdKeepAndClose_Click()

UserForm1.Hide

End Sub

Private Sub cmdSelect_Click()

'cacher l'IHM
UserForm1.Hide

'définition de la pièce active comme pièce d'étude
Dim oPartDocument As PartDocument
Dim oPart As Part
Set oPartDocument = CATIA.ActiveDocument
Set oPart = oPartDocument.Part

'définition de l'objet sélection et annulation des sélections effectuées préalablement
Dim oSelection 'As Selection
Set oSelection = oPartDocument.Selection
oSelection.Clear

'début du code nécessaire pour la sélection d'un objet par l'utilisateur
Dim inputObjectType(0)  'ceci est un tableau composé d'un élément
Dim status As String
inputObjectType(0) = UserForm1.cmbType.SelText
status = oSelection.SelectElement2(inputObjectType, "Merci de sélectionner une esquisse", True)

'récupération de l'élément sélectionné dans un objet oResult
Dim oResult

Set oResult = oSelection.Item(1).Value

'Affichage du nom de l'élément sélectionné
UserForm1.txtResult.Text = oResult.Name

'montrer l'IHM
UserForm1.Show

End Sub


Private Sub UserForm_Initialize()
'Ajout d'éléments dans la liste de choix des types d'éléments sélectionnés
cmbType.AddItem "Point"
cmbType.AddItem "Sketch"
cmbType.AddItem "Plane"
cmbType.Value = "Sketch"
End Sub
